FME workspace example_2_bulk_attribute_feature_managing.fmw

Parameters:
- DestDataset_SQLITE3 = $(FME_MF_DIR)table.db   # SQLite Database

Writers:
- SQLITE3_1: SQLITE3 to $(DestDataset_SQLITE3)

Creator
    GEOMTYPE = Geometry Object
    NUM = 99
    CREATED -> SchemaMapper
Junction
    -> PythonCaller_2
PythonCaller_2
    NEW_ATTRIBUTES = ref_Soda ref_Name ref_ID
    PYTHONSOURCE:
      import fme
      import fmeobjects

      # Template Class Interface:
      # When using this class, make sure its name is set as the value of
      # the 'Class or Function to Process Features' transformer parameter
      class FeatureProcessor(object):
          def __init__(self):
              self.unique_attributes = dict()
              self.feature_list = []

          def input(self,feature):
              for attribute_name in feature.getAllAttributeNames():
                  if attribute_name not in self.unique_attributes.keys():
                      self.unique_attributes[attribute_name] = set()
                      self.unique_attributes[attribute_name].add(feature.getAttribute(attribute_name))
                  else:
                      self.unique_attributes[attribute_name].add(feature.getAttribute(attribute_name))
              self.feature_list.append(feature)

          def close(self):

              # Tranform every set into list
              # preserves index
              for key, value in self.unique_attributes.items():
                  self.unique_attributes[key] = list(value)


              for feature in self.feature_list:
                  for attribute_name, value_list in self.unique_attributes.items():

                      key = feature.getAttribute(attribute_name)
                      feature.setAttribute(f'ref_{attribute_name}', value_list.index(key))
                  self.pyoutput(feature)
              for attribute_name, value_list in self.unique_attributes.items():
                  for index, key in enumerate(value_list):
                      newFeature = fmeobjects.FMEFeature()
                      newFeature.setAttribute('fme_feature_type', f'{attribute_name}_table')
                      newFeature.setAttribute(attribute_name, key)
                      newFeature.setAttribute(f'ref_{attribute_name}', index)
                      self.pyoutput(newFeature)
    PYTHONSYMBOL = FeatureProcessor
    -> FeatureTypeFilter_2
FeatureTypeFilter_2
    ATTRIBUTES = <Blank>,<Unfiltered>,Soda_table,Name_table,ID_table
    <UNFILTERED> -> Tester
    Soda_table -> soda_table (writer SQLITE3_1)
    Name_table -> name_table (writer SQLITE3_1)
    ID_table -> id_table (writer SQLITE3_1)
Note: Silly, because its unique data
Tester
    BOOL_OP = OR
    COMPOSITE_TEST = 1
    TEST_CLAUSE = TEST ID ATTRIBUTE_HAS_A_VALUE ""
    TEST_MODE = TEST
    PASSED -> main_data_table (writer SQLITE3_1)

Bookmark: Create some unique names
SchemaMapper
    CSV2_CASE_SENSITIVE_FIELD_NAMES = Yes
    CSV2_DATA_START_LINE = 2
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(FME_MF_DIR)schema_file.csv
    FORMAT = CSV2
    IDXDESTATTR = fme_feature_type
    IDXDESTCOL = ""
    IDXSOURCEATTR = fme_feature_type
    IDXSOURCECOL = ""
    MAP_ATTRS = """""" destinationAttributeName destinationAttributeValue
    MATCH_ATTRS = sourceAttributeName sourceAttributeValue
    ROW_ID_ATTR = _schemamapper_row_ids
    TABLE = CSV
    MAPPED -> AttributeExposer
AttributeExposer
    ATTR_LIST = Name
    -> AttributeRemover
AttributeRemover
    REMOVE_ATTRS = _schemamapper_row_ids
    -> Sampler

Bookmark: Lets build lots of rendundant data
Sampler
    RATE = 3
    SAMPLE_MODE = No
    SAMPLE_TYPE_LONG = Every Nth Feature
    SAMPLED -> AttributeCreator_3
    NOT_SAMPLED -> Sampler_2
Note: AttributeCreator_3 [AttributeCreator] / Attributes To Create: New AttributeAttribute ValueSodaSolo
AttributeCreator_3
    ATTR_TABLE = SET_TO Soda = Solo
    -> Junction
Sampler_2
    RATE = 2
    SAMPLE_MODE = No
    SAMPLE_TYPE_LONG = Every Nth Feature
    SAMPLED -> AttributeCreator_2
    NOT_SAMPLED -> AttributeCreator
Note: AttributeCreator_2 [AttributeCreator] / Attributes To Create: New AttributeAttribute ValueSodaPepsi
AttributeCreator_2
    ATTR_TABLE = SET_TO Soda = Pepsi
    -> Junction
Note: AttributeCreator [AttributeCreator] / Attributes To Create: New AttributeAttribute ValueSodaCola
AttributeCreator
    ATTR_TABLE = SET_TO Soda = Cola
    -> Junction

Bookmark: Main table with all records
main_data_table (writer SQLITE3_1)
    attributes: Soda varchar(200), ID varchar(200), Name varchar(200), ref_Soda varchar(200), ref_Name varchar(200), ref_ID varchar(200)

Bookmark: Relational datatable
soda_table (writer SQLITE3_1)
    attributes: Soda varchar(200), ref_Soda varchar(200)

Bookmark: Silly, just as an example.
name_table (writer SQLITE3_1)
    attributes: Name varchar(200), ref_Name varchar(200)
id_table (writer SQLITE3_1)
    attributes: ID varchar(200), ref_ID varchar(200)
