FME workspace shutdown_script.fmw
Shutdown Python:
      import os


      CURRENT_PATH = FME_MacroValues['FME_MF_DIR_DOS']

      some_deleted = False
      deleted_files = []
      try:
          for _file in os.listdir(CURRENT_PATH):
              if '_pytmp_' in _file:
                  abs_path = os.path.join(CURRENT_PATH, _file)
                  os.remove(abs_path)
                  deleted_files.append(_file)
                  some_deleted = True
          deleted_files = '\n'.join(deleted_files)
          if some_deleted:
              print(f'Following files has been cleaned: {deleted_files}', 0)
      except Exception as e:
          print(f'{str(e)}',2)

PythonCreator
    PYTHONSOURCE_NEW:
      import os

      class Pass(object):
          def __init__(self):
              pass
          def input(self, feature):
              pass
          def close(self):
              pass
      current_path = FME_MacroValues['FME_MF_DIR_DOS']
      tmpfile = open('_pytmp_sdg', 'w')
      tmpfile.write('Hello World\n')
      tmpfile.close()
    PYTHONSYMBOL = Pass
