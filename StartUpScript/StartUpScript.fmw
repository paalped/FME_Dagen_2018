FME workspace StartUpScript.fmw
Startup Python:
      import fmeobjects
      import os

      INFO = fmeobjects.FME_INFORM # 0
      WARN = fmeobjects.FME_WARN # 1
      ERROR = fmeobjects.FME_ERROR # 2

      logger = fmeobjects.FMELogFile()

      CURRENT_PATH = FME_MacroValues['FME_MF_DIR_DOS']
      WORKSPACE_NAME = FME_MacroValues['FME_MF_NAME']

      CONFIGFILE = f'{WORKSPACE_NAME}_config.xml'.replace('.fmw','')

      if os.path.isfile(CONFIGFILE):
          logger.logMessageString('Configfile ok', INFO)

      else:
          abs_path = os.path.join(CURRENT_PATH, CONFIGFILE)
          logger.logMessageString(f'Missing file: {abs_path}', ERROR)
          raise FileNotFoundError(f'Missing file: {abs_path}')

Note: Heavy workspace
Creator
    GEOMTYPE = Geometry Object
    NUM = 1
