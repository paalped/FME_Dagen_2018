FME workspace ScriptedPythonParameter.fmw

Parameters:
- username:   # Python Script
      import fmeobjects
      import os
      import xml.etree.ElementTree as ET
      
      INFO = fmeobjects.FME_INFORM # 0
      WARN = fmeobjects.FME_WARN # 1
      ERROR = fmeobjects.FME_ERROR # 2
      
      logger = fmeobjects.FMELogFile()
      
      CURRENT_PATH = FME_MacroValues['FME_MF_DIR_DOS']
      _, CURRENT_DIR = os.path.split(CURRENT_PATH)
      FILENAME = FME_MacroValues['FME_MF_NAME']
      
      CONFIGFILE = f'{FILENAME}_config.xml'.replace('.fmw','')
      
      if os.path.isfile(CONFIGFILE):
          logger.logMessageString('Configfile ok', INFO)
          tree = ET.parse(os.path.join(CURRENT_PATH, CONFIGFILE))
          root = tree.getroot()
          for host in root.findall('host'):
              logger.logMessageString(str(host), 1)
              for child in host:
                  if child.tag == 'username' and child.attrib['name'] == CURRENT_DIR:
                      return child.text
      else:
          logger.logMessageString(f'file don\'t exists: {os.path.join(CURRENT_PATH, CONFIGFILE)}', ERROR)
          #return f'Missing Config file: {os.path.join(CURRENT_PATH, CONFIGFILE)}'

Creator
    GEOMTYPE = Geometry Object
    NUM = 1
    CREATED -> ParameterFetcher
ParameterFetcher
    ATTR_LIST = _username $(username)
    -> ParameterFetcher_Output
ParameterFetcher_Output: Inspector
