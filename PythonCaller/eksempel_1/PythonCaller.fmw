FME workspace PythonCaller.fmw

Parameters:
- DestDataset_SQLITE3 = $(FME_MF_DIR)table.db   # SQLite Database

Writers:
- SQLITE3_1: SQLITE3 to $(DestDataset_SQLITE3)

Creator
    GEOMTYPE = Geometry Object
    NUM = 99
    CREATED -> AttributeCreator_4
Note: Fictive data
AttributeCreator_4
    ATTR_TABLE = SET_TO Name = Rosalinda
    -> Sampler
Junction
    -> PythonCaller
Note: import fmeobjects / class FeatureProcessor(object): / def __init__(self): / # Initializes before first feature / self.unique_attributes = set() / self.feature_list = [] / def input(self,feature): / # Runs per feature / self.unique_attributes.add(feature.getAttribute('Soda')) / self.feature_list.append(feature) / def close(self): / # Runs after last feature has passed / attribute_values = list(self.unique_attributes) / for feature in self.feature_list: / attribute_value = feature.getAttribute('Soda') / feature.setAttribute('ref_Soda', attribute_values.index(attribute_value)) / self.pyoutput(feature) / for index, attribute_value in enumerate(attribute_values): / newFeature = fmeobjects.FMEFeature() / newFeature.setAttribute('fme_feature_type', 'soda_table') / newFeature.setAttribute('Soda', attribute_value) / newFeature.setAttribute('ref_Soda', index) / self.pyoutput(newFeature)
PythonCaller
    NEW_ATTRIBUTES = ref_Soda
    PYTHONSOURCE:
      import fme
      import fmeobjects

      # Template Class Interface:
      # When using this class, make sure its name is set as the value of
      # the 'Class or Function to Process Features' transformer parameter
      class FeatureProcessor(object):
          def __init__(self):
              self.unique_attributes = set()
              self.feature_list = []

          def input(self,feature):
              self.unique_attributes.add(feature.getAttribute('Soda'))
              self.feature_list.append(feature)

          def close(self):
              keys = list(self.unique_attributes)

              for feature in self.feature_list:
                  key = feature.getAttribute('Soda')
                  feature.setAttribute(f'ref_Soda', keys.index(key))
                  self.pyoutput(feature)

              for index, key in enumerate(keys):
                  newFeature = fmeobjects.FMEFeature()
                  newFeature.setAttribute('fme_feature_type', 'soda_table')
                  newFeature.setAttribute('Soda', key)
                  newFeature.setAttribute('ref_Soda', index)
                  self.pyoutput(newFeature)
    PYTHONSYMBOL = FeatureProcessor
    -> FeatureTypeFilter
FeatureTypeFilter
    ATTRIBUTES = <Blank>,<Unfiltered>,soda_table
    <BLANK> -> AttributeRemover
    <UNFILTERED> -> AttributeRemover
    soda_table -> AttributeRemover_2
AttributeRemover
    REMOVE_ATTRS = Soda
    -> main_data_table (writer SQLITE3_1)
main_data_table (writer SQLITE3_1)
    attributes: Name varchar(200), ID varchar(200), ref_Soda varchar(200)
AttributeRemover_2
    REMOVE_ATTRS = ID,Name
    -> soda_table (writer SQLITE3_1)
soda_table (writer SQLITE3_1)
    attributes: Soda varchar(200), ref_Soda varchar(200)

Bookmark: Lets build lots of rendundant data
Sampler
    RATE = 3
    SAMPLE_MODE = No
    SAMPLE_TYPE_LONG = Every Nth Feature
    SAMPLED -> AttributeCreator_3
    NOT_SAMPLED -> Sampler_2
Note: AttributeCreator_3 [AttributeCreator] / Attributes To Create: New AttributeAttribute ValueSodaSolo
AttributeCreator_3
    ATTR_TABLE = SET_TO Soda = Solo
    -> Junction
Sampler_2
    RATE = 2
    SAMPLE_MODE = No
    SAMPLE_TYPE_LONG = Every Nth Feature
    SAMPLED -> AttributeCreator_2
    NOT_SAMPLED -> AttributeCreator
Note: AttributeCreator_2 [AttributeCreator] / Attributes To Create: New AttributeAttribute ValueSodaPepsi
AttributeCreator_2
    ATTR_TABLE = SET_TO Soda = Pepsi
    -> Junction
Note: AttributeCreator [AttributeCreator] / Attributes To Create: New AttributeAttribute ValueSodaCola
AttributeCreator
    ATTR_TABLE = SET_TO Soda = Cola
    -> Junction
